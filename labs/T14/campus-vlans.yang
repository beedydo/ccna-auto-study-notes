module campus-vlans {
  yang-version 1.1;
  namespace "urn:ccna-auto:yang:campus-vlans";
  prefix cv;

  import ietf-interfaces {
    prefix if;
  }
  import ietf-inet-types {
    prefix inet;
  }

  organization
    "CCNA Automation study group";
  contact
    "Bob (T14 owner)";
  description
    "Teaching module for T14: one of every node type you must read.";

  revision 2026-10-10 {
    description
      "Initial revision.";
  }

  typedef vlan-id {
    type uint16 {
      range "1..4094";
    }
    description
      "IEEE 802.1Q VLAN ID.";
  }

  identity vlan-role;

  identity user {
    base vlan-role;
  }

  identity voice {
    base vlan-role;
  }

  grouping packet-counters {
    leaf in-packets {
      type uint64;
    }
    leaf out-packets {
      type uint64;
    }
  }

  container vlans {
    list vlan {
      key "id";
      leaf id {
        type vlan-id;
      }
      leaf name {
        type string {
          length "1..32";
        }
        mandatory true;
      }
      leaf role {
        type identityref {
          base vlan-role;
        }
      }
      leaf admin-state {
        type enumeration {
          enum active;
          enum suspend;
        }
        default "active";
      }
      leaf gateway {
        type union {
          type inet:ipv4-address;
          type enumeration {
            enum none;
          }
        }
      }
      leaf-list dhcp-helper {
        type inet:ipv4-address;
      }
      container statistics {
        config false;
        uses packet-counters;
      }
    }
  }

  augment "/if:interfaces/if:interface" {
    leaf access-vlan {
      type leafref {
        path "/cv:vlans/cv:vlan/cv:id";
      }
    }
  }
}
